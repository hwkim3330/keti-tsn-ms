// Copyright (c) 2021-2022 Microchip Technology Inc. and its subsidiaries.
//
// Unpublished rights reserved under the copyright laws of the United States
// of America, other countries and international treaties. Permission to use,
// copy, store and modify, the software and its source code is granted but
// only in connection with products utilizing the Microsemi switch and PHY
// products.  Permission is also granted for you to integrate into other
// products, disclose, transmit and distribute the software only in an
// absolute machine readable format (e.g. HEX file) and only in or with
// products utilizing the Microsemi switch and PHY products.  The source code
// of the software may not be disclosed, transmitted or distributed without
// the prior written permission of Microsemi.
//
// This copyright notice must appear in any copy, modification, disclosure,
// transmission or distribution of the software.  Microsemi retains all
// ownership, copyright, trade secret and proprietary rights in the software
// and its source code, including all modifications thereto.
//
// THIS SOFTWARE HAS BEEN PROVIDED "AS IS". MICROSEMI HEREBY DISCLAIMS ALL
// WARRANTIES OF ANY KIND WITH RESPECT TO THE SOFTWARE, WHETHER SUCH
// WARRANTIES ARE EXPRESS, IMPLIED, STATUTORY OR OTHERWISE INCLUDING, WITHOUT
// LIMITATION, WARRANTIES OF MERCHANTABILITY, FITNESS FOR A PARTICULAR USE OR
// PURPOSE AND NON-INFRINGEMENT.

module ieee802-dot1ab-lldp-dev {
    yang-version 1.1;
    namespace "urn:mchp:params:xml:ns:yang:ieee802-dot1ab-lldp-dev";
    prefix ieee802-dot1ab-lldp-dev-pre;

    import ieee802-dot1ab-lldp {
        prefix lldp;
    }

    revision 2024-04-12 {
    }

    deviation /lldp:lldp/lldp:local-system-data {
        deviate not-supported;
    }

    deviation /lldp:lldp/lldp:notification-interval {
        deviate not-supported;
    }

    deviation /lldp:lldp/lldp:port/lldp:management-address-tx-port {
        deviate not-supported;
    }

    deviation /lldp:lldp/lldp:port/lldp:message-fast-tx {
        deviate not-supported;
    }

    deviation /lldp:lldp/lldp:port/lldp:message-tx-hold-multiplier {
        deviate not-supported;
    }

    deviation /lldp:lldp/lldp:port/lldp:message-tx-interval {
        deviate not-supported;
    }

    deviation /lldp:lldp/lldp:port/lldp:notification-enable {
        deviate not-supported;
    }

    deviation /lldp:lldp/lldp:port/lldp:notification-interval {
        deviate not-supported;
    }

    deviation /lldp:lldp/lldp:port/lldp:port-desc {
        deviate not-supported;
    }

    deviation /lldp:lldp/lldp:port/lldp:port-id {
        deviate not-supported;
    }

    deviation /lldp:lldp/lldp:port/lldp:port-id-subtype {
        deviate not-supported;
    }

    deviation /lldp:lldp/lldp:port/lldp:reinit-delay {
        deviate not-supported;
    }

    deviation /lldp:lldp/lldp:port/lldp:remote-systems-data/lldp:remote-changes {
        deviate not-supported;
    }

    deviation /lldp:lldp/lldp:port/lldp:remote-systems-data/lldp:remote-too-many-neighbors {
        deviate not-supported;
    }

    deviation /lldp:lldp/lldp:port/lldp:remote-systems-data/lldp:remote-unknown-tlv {
        deviate not-supported;
    }

    deviation /lldp:lldp/lldp:port/lldp:rx-statistics/lldp:total-ageouts {
        deviate not-supported;
    }

    deviation /lldp:lldp/lldp:port/lldp:tlvs-tx-enable {
        deviate not-supported;
    }

    deviation /lldp:lldp/lldp:port/lldp:tx-credit-max {
        deviate not-supported;
    }

    deviation /lldp:lldp/lldp:port/lldp:tx-fast-init {
        deviate not-supported;
    }

    deviation /lldp:lldp/lldp:port/lldp:tx-statistics/lldp:total-length-errors {
        deviate not-supported;
    }

    deviation /lldp:lldp/lldp:reinit-delay {
        deviate not-supported;
    }

    deviation /lldp:lldp/lldp:remote-statistics {
        deviate not-supported;
    }

    deviation /lldp:lldp/lldp:tx-credit-max {
        deviate not-supported;
    }

    deviation /lldp:remote-table-change {
        deviate not-supported;
    }

    deviation /lldp:lldp/lldp:message-fast-tx {
        deviate replace {
            config false;
        }
    }

    deviation /lldp:lldp/lldp:message-tx-hold-multiplier {
        deviate replace {
            config false;
        }
    }

    deviation /lldp:lldp/lldp:message-tx-interval {
        deviate replace {
            config false;
        }
    }

    deviation /lldp:lldp/lldp:tx-fast-init {
        deviate replace {
            config false;
        }
    }

}
